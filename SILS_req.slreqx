# SILS_req

## #1: ToF Distance Value를 이용한 Reference Velocity 제어 (Functional)

### #14: ToF 센서를 활용하여 차량 왼쪽 벽과의 거리를 측정한다. (Functional)

### #15: ToF 센서를 통해 측정한 데이터는 UART를 통해 받아온다. (Functional)

### #16: ToF 센서는 차량 왼쪽에 장착한다. (Functional)

### #18: ToF 센서는 적어도 100ms마다 벽과의 거리를 측정해야 한다. (Functional)

### #19: ToF 센서로 측정한 데이터의 오차는 10%를 초과하면 안된다. (Functional)

### #20: ToF 센서로 측정한 데이터의 자료형은 Float이어야 한다. (Functional)

### #21: 측정한 데이터값을 전송하는 delay는 10ms보다 작아야 한다. (Functional)

### #24: LPF를 거친 벽과의 거리를 통해 차량의 경로를 계산할 수 있어야 한다. (Functional)

### #25: 벽과의 거리 기준값과 10% 이내로 차이나는 경우, 현재 벽과의 거리는 기준값으로 넘겨준다. (Functional)

### #26: Differential Drive Kinematics에 기반하여 바퀴의 속도를 계산하고 갱신해야 한다. (Functional)

### #27: 차량이 우회전 해야하는 경우 R값과 각속도 w의 값을 계산하여 새로운 바퀴의 속도를 계산한다 (Functional)

### #28: 차량이 좌회전 해야하는 경우 R값과 각속도 w의 값을 계산하여 새로운 바퀴의 속도를 계산한다. (Functional)

## #2: DCMotor Encoder Value를 이용한 Velocity 도출 (Functional)

### #4: 양쪽 모터의 Encoder를 통해 현재 모터의 각속도를 측정한다. (Functional)

### #29: Encoder는 적어도 10ms마다 현재 모터의 각속도를 측정해야한다. (Functional)

### #30: Encoder로 측정한 데이터의 오차는 10%를 초과하면 안된다. (Functional)

### #31: Encoder로 측정한 데이터의 자료형은 Float이어야 한다. (Functional)

## #5: DCMotor PID 제어 (Functional)

### #37: 현재 차량이 벽과 멀어지는 경우 차량이 좌회전하도록 속도를 갱신한다. (Functional)

### #38: 현재 차량이 벽과 가까워지는 경우 차량이 우회전하도록 속도를 갱신한다. (Functional)

### #39: 현재 차량과 벽과의 거리, 왼쪽 바퀴의 속도, 오른쪽 바퀴의 속도를 받아와 새로운 바퀴의 속도를 계산해야 한다. (Functional)

### #40: 계산을 통해 도출된 새로운 바퀴의 속도는 모터 PI 제어의 ref 값으로 사용한다. (Functional)

### #41: PI 제어를 통해 모터 출력의 오차를 10%로 유지해야 한다. (Functional)

## #6: Low Pass Filter (Functional)

### #42: ToF 센서로 측정한 데이터에는 LPF를 적용해야 한다. (Functional)

### #43: Encoder로 측정한 데이터에는 LPF를 적용해야 한다. (Functional)

## #7: DCMotor PWM 제어 (Functional)

### #45: DC모터의 속도 제어는 GTM을 이용한 PWM으로 한다. (Functional)

## #8: Observer 제어 및 기타 (Functional)

### #46: 주행 중이면 LED1을 켠다. (Functional)

### #47: 주행 중이지 않으면 LED1을 끈다. (Functional)

### #48: 관측기는 TC275 환경을 고려하여 discrete 해야 한다. (Functional)

### #49: state-feedback controller는 관측기로 예측한 값을 활용한다. (Functional)

### #50: 관측기는 DC모터의 엔코더 값으로 각속도, 전류 값을 예측한다. (Functional)

### #51: state-feedback controller는 기준 각속도 값을 위한 전압 값을 생성한다. (Functional)
